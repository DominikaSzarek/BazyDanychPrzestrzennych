FME workspace zad3_4.fmw

Parameters:
- DestDataset_POSTGIS_RASTER =
- SourceDataset_SHAPEFILE_3 =
- SourceDataset_TIFF_3 =

Readers:
- TIFF_2: TIFF from $(SourceDataset_TIFF_3)
- SHAPEFILE_2: SHAPEFILE from $(SourceDataset_SHAPEFILE_3)

Writers:
- POSTGIS_RASTER_1: POSTGIS_RASTER to $(DestDataset_POSTGIS_RASTER)

Note: zad.3
Note: zad. 4 / Select st_union(rast) into rasters_union from public."Exports";
Exports (writer POSTGIS_RASTER_1)
    attributes: _clipped char(3)

Bookmark: Reader Feature Types
scotland_and_wales_region (reader SHAPEFILE_2)
    attributes: NAME varchar(100), AREA_CODE varchar(3), DESCRIPTIO varchar(50), FILE_NAME varchar(100), NUMBER number(11,0), NUMBER0 number(11,0), POLYGON_ID number(11,0), UNIT_ID number(11,0), CODE varchar(9), HECTARES float, AREA float, TYPE_CODE varchar(2), DESCRIPT0 varchar(25), TYPE_COD0 varchar(3), DESCRIPT1 varchar(36)
    -> Tester

Bookmark: Process
Tester
    BOOL_OP = OR
    COMPOSITE_TEST = 1
    TEST_CLAUSE = CASE_INSENSITIVE_TEST @Value(NAME) BEGINS_WITH South Wales
    TEST_MODE = CASE_INSENSITIVE_TEST
    PASSED -> Aggregator
Aggregator
    ACCUM_ATTRS_NAME = Use Attributes From One Feature
    AGGREGATE_TYPE = Homogeneous Collection (If Possible)
    ATTR_TO_TRAIT = Yes
    ID_SELECTION = ID and Parent ID
    MODE = Geometry - Assemble One Level
    PRESERVE_ID = No
    SEP = ,
    AGGREGATE -> Clipper [CLIPPER]
Clipper
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> RasterPaletteResolver
RasterPaletteResolver
    -> Exports (writer POSTGIS_RASTER_1)

Bookmark: Readers
TIFF (reader TIFF_2)
    -> Clipper [CLIPPEE]
